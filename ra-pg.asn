-- 
--  Copyright 2017 Crash Avoidance Metrics Partner, VSC5 Consortium
-- 
--  Licensed under the Apache License, Version 2.0 (the "License");
--  you may not use this file except in compliance with the License.
--  You may obtain a copy of the License at
-- 
--     http://www.apache.org/licenses/LICENSE-2.0
-- 
--  Unless required by applicable law or agreed to in writing, software
--  distributed under the License is distributed on an "AS IS" BASIS,
--  WITHOUT WARRANTIES OR CONDITIONS OF ANY KIND, either express or implied.
--  See the License for the specific language governing permissions and
--  limitations under the License.
-- 

-- @namespace Ieee1609Dot2RaPgInterface
Ieee1609Dot2RaPgInterface
{iso(1) identified-organization(3) ieee(111) 
standards-association-numbered-series-standards(2) wave-stds(1609) dot2(2)
scms(2) interfaces(1) ra-pg(16)}

DEFINITIONS AUTOMATIC TAGS ::= BEGIN 

EXPORTS ALL;
 
IMPORTS 
  HashedId8,
  Hostname,
  Opaque, 
  Uint8,
  Uint32
FROM IEEE1609dot2BaseTypes {iso(1) identified-organization(3) ieee(111) 
    standards-association-numbered-series-standards(2) wave-stds(1609) dot2(2)
    base(1) base-types(2)}

  Countersignature,
  SignerIdentifier
FROM IEEE1609dot2 {iso(1) identified-organization(3) ieee(111) 
    standards-association-numbered-series-standards(2) wave-stds(1609) dot2(2)
    base(1) schema(1)}

  HPCR,
  HPCRAndHostInfo,
  LCIAndHostInfo,
  RaHostnameId,
  MaHostnameId
FROM Ieee1609dot2ScmsBaseTypes {iso(1) identified-organization(3) ieee(111)
    standards-association-numbered-series-standards(2) wave-stds(1609) dot2(2)
    scms(2) interfaces(1) base-types(2)}

  ScopedMaRaBlacklistError,
  ScopedMaRaLCIError
FROM Ieee1609dot2ScmsError {iso(1) identified-organization(3) ieee(111)
    standards-association-numbered-series-standards(2) wave-stds(1609) dot2(2)
    scms(2) errors(2) complete(1)}
    
  RaPgError
FROM Ieee1609Dot2RaPgError {iso(1) identified-organization(3) ieee(111) 
    standards-association-numbered-series-standards(2) wave-stds(1609)  
    dot2(2) scms(2) errors(2) ra-pg(16)}

  BasePolicyFile,
  ToBeSignedPolicyData
FROM Ieee1609dot2ScmsPolicyTypes {iso(1) identified-organization(3) ieee(111)
    standards-association-numbered-series-standards(2) wave-stds(1609)  dot2(2)
    scms (2) interfaces(1) policy-types (500)}
;

---
-- @brief The RaPgInterfacePDU is the parent message type for messages sent
--        between Registration Authority (RA) and Policy Generator (PG).
-- @class RaPgInterfacePDU 
-- @param raPgPolicySignatureRequest      contains the request from RA to
--                                        obtain policy file from PG.
-- @param raPgPolicySignatureRequestReply contains response from PG to
--                                        RaPgPolicySignatureRequestMsg from RA.
RaPgInterfacePDU ::= CHOICE {
    raPgPolicySignatureRequest   RaPgPolicySignatureRequestMsg,
    raPgPolicySignatureRequestReply  RaPgPolicySignatureRequestReplyMsg,
    ...
}

---
-- @brief This data type contains custom policy files generated by PG. PG
--        signs this at the scms-protocol level.
-- @class ToBeSignedCustomPolicyFile 
-- @param policy denotes the custom policy file generated by PG.
ToBeSignedCustomPolicyFile ::= ToBeSignedPolicyData( WITH COMPONENTS {...,
    policy(WITH COMPONENTS {...,
        custom PRESENT
    })
})

---
-- @brief This data type is used by PG to enclose custom policy file.
-- @class SignedCustomPolicyFile 
-- @param tbsData is the custom policy file data that is signed by PG at
--                scms-protocol level.
SignedCustomPolicyFile ::= BasePolicyFile (WITH COMPONENTS {...,
    tbsData( WITH COMPONENTS {...,
        policy(WITH COMPONENTS {...,
            custom PRESENT
        })
    })
})

---
-- @brief RA uses this data type to request signed modified global parameters
--        inside a local policy file (LPF). An RA may generate an LPF with a
--        mix of global parameters and local parameters.  The global portion
--        must be approved and signed by the PG before it can be distributed
--        to EEs.  
-- @class RaPgPolicySignatureRequestMsg 
-- @param version contains the current version of the data type. The version 
--                specified in this document is version 1, represented by the
--                integer 1.
-- @param tbs     contains the policy file data that is signed by PG.
-- @see Uint8
RaPgPolicySignatureRequestMsg ::= SEQUENCE {
    version    Uint8(1),
    tbs        ToBeSignedCustomPolicyFile,
    ...
}


---
-- @brief PG uses this data type to respond to RaPgPolicySignatureRequestMsg
--        from RA.
-- @class RaPgPolicySignatureRequestReplyMsg 
-- @param version    contains the current version of the data type. The version 
--                   specified in this document is version 1, represented by 
--                   the integer 1.
-- @param signedFile includes the policy file signed by PG if request from RA
--                   has no errors. Otherwise, an appropriate error code is
--                   included.
-- @see Uint8, RaPgError
RaPgPolicySignatureRequestReplyMsg ::= SEQUENCE {
    version    Uint8(1),
    signedFile   CHOICE {
       success       SignedCustomPolicyFile,
       failure       RaPgError
    }
}


END
