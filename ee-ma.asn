--
--  Copyright 2017 Crash Avoidance Metrics Partner, VSC5 Consortium
--
--  Licensed under the Apache License, Version 2.0 (the "License");
--  you may not use this file except in compliance with the License.
--  You may obtain a copy of the License at
--
--     http://www.apache.org/licenses/LICENSE-2.0
--
--  Unless required by applicable law or agreed to in writing, software
--  distributed under the License is distributed on an "AS IS" BASIS,
--  WITHOUT WARRANTIES OR CONDITIONS OF ANY KIND, either express or implied.
--  See the License for the specific language governing permissions and
--  limitations under the License.
--

-- @namespace Ieee1609Dot2EndEntityMaInterface
Ieee1609Dot2EndEntityMaInterface
{iso(1) identified-organization(3) ieee(111)
standards-association-numbered-series-standards(2) wave-stds(1609)
dot2(2) scms(2) interfaces(1) ee-ma (7)}

DEFINITIONS AUTOMATIC TAGS ::= BEGIN

EXPORTS ALL;

IMPORTS
  Opaque,
  Signature,
  Time32,
  ThreeDLocation,
  Uint8
FROM IEEE1609dot2BaseTypes {iso(1) identified-organization(3) ieee(111)
		standards-association-numbered-series-standards(2) wave-stds(1609)
		dot2(2) base(1) base-types(2)}

;

---
-- @brief The EndEntityMaInterfacePDU is the parent message type for messages sent between End
--        Entities (EE) and the Misbehavior Authority (MA).
-- @class EndEntityMaInterfacePDU
-- @param misbehaviorReport contains the misbehavior report sent by an end entity to the MA.
EndEntityMaInterfacePDU::= CHOICE {
    misbehaviorReport   MisbehaviorReportContents,
    ...
}

---
-- @brief This data type contains the structure of a misbehavior report sent by an end entity to the MA.
-- @class MisbehaviorReportContents
-- @param version               contains the current version of the data type. The version specified
--                              in this document is version 1, represented by the integer 1.
-- @param misbehavingDeviceInfo opaque and currently unused.
-- @param misbehavingDeviceBSMs contains BSMs of an alleged, misbehaving EE in the form of an array
--                              of BSMs.
-- @param reporterDeviceBSMs    contains BSMs of the reporting EE in the form of an array of BSMs.
-- @param sensorInfo            opaque and currently unused.
-- @see Uint8, Opaque, BasicSafetyMessage
MisbehaviorReportContents ::= SEQUENCE {
    version Uint8(1),
    misbehavingDeviceInfo Opaque, -- placeholder
    misbehavingDeviceBSMs OCTET STRING OPTIONAL, -- non-OER encoded ASN.1 messages
    reporterDeviceBSMs OCTET STRING OPTIONAL, -- non-OER encoded ASN.1 messages
    sensorInfo Opaque OPTIONAL, -- placeholder: non-V2V related sensor information, if available
    ...
}




END
