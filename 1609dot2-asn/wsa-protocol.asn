IEEE1609dot2WsaProtocol {iso(1) identified-organization(3) ieee(111) 
standards-association-numbered-series-standards(2) wave-stds(1609)  
dot2(2) wsa(4) protocol(1)}

DEFINITIONS AUTOMATIC TAGS ::= BEGIN 

EXPORTS ALL;
 
IMPORTS 
  CrlSeries,
  EccNistP256CurvePoint,
  EciesNistP256EncryptedKey,
  GeographicRegion,
  HashedId10,
  HashedId8,
  IValue,
  Opaque,
  PKAlgorithm,
  Psid,
  PsidSsp,
  SequenceOfPsid,
  SequenceOfPsidSspRange,
  Signature,
  ThreeDLocation,
  Time32,
  Time64,
  Time64WithStandardDeviation,
  Uint16, 
  Uint3,
  Uint32,
  Uint8,
  ValidityPeriod
FROM IEEE1609dot2BaseTypes {iso(1) identified-organization(3) ieee(111) 
    standards-association-numbered-series-standards(2) wave-stds(1609)  
    dot2(2) base(1) base-types(2)}
;

--

  WsaSsp::= SEQUENCE {
      version                Uint8(1),
      advertiserPermissions  AdvertiserPermissions OPTIONAL,
      providerPermissions    ProviderPermissions OPTIONAL,
      ...
  }
      
  AdvertiserPermissions ::= SEQUENCE OF ChannelIdentifier

  ChannelIdentifier ::= SEQUENCE {
      countryString          OCTET STRING (SIZE(3)),
      operatingClass         Uint8,
      channelNumber          Uint8
  }

  ProviderPermissions ::= SEQUENCE OF ChannelSpecificProviderPermission

  ChannelSpecificProviderPermission ::= SEQUENCE {
      channelId                ChannelIdentifier,
      permittedPsids           SequenceOfPsid OPTIONAL,
      permittedPsidSspRange    SequenceOfPsidSspRange OPTIONAL,
      permittedEdcaParameters  SequenceOfEdcaIdentifier OPTIONAL,
      ...
  }

  EdcaIdentifier ::= CHOICE {
      enum                     EnumeratedEdcaIdentifier,
      explicit                 ExplicitEdcaIdentifier,
      ...
  }

  EnumeratedEdcaIdentifier ::= ENUMERATED {us-j2945-bsm (0), ... }

  ExplicitEdcaIdentifier ::= SEQUENCE {
      qosInfo                  Uint8,
      reserved                 Uint8,
      set1                     OCTET STRING (SIZE(4)),
      set2                     OCTET STRING (SIZE(4)),
      set3                     OCTET STRING (SIZE(4)),
      set4                     OCTET STRING (SIZE(4))
  }

  SequenceOfEdcaIdentifier ::= SEQUENCE OF EdcaIdentifier

END
