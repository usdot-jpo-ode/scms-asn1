--
--  Copyright 2017 Crash Avoidance Metrics Partner, VSC5 Consortium
--
--  Licensed under the Apache License, Version 2.0 (the "License");
--  you may not use this file except in compliance with the License.
--  You may obtain a copy of the License at
--
--     http://www.apache.org/licenses/LICENSE-2.0
--
--  Unless required by applicable law or agreed to in writing, software
--  distributed under the License is distributed on an "AS IS" BASIS,
--  WITHOUT WARRANTIES OR CONDITIONS OF ANY KIND, either express or implied.
--  See the License for the specific language governing permissions and
--  limitations under the License.
--

-- @namespace Ieee1609Dot2PcaRaInterface
Ieee1609Dot2PcaRaInterface
{iso(1) identified-organization(3) ieee(111)
standards-association-numbered-series-standards(2) wave-stds(1609) dot2(2)
scms(2) interfaces(1) pca-ra(15)}

DEFINITIONS AUTOMATIC TAGS ::= BEGIN

EXPORTS ALL;


IMPORTS
  Duration,
  EccP256CurvePoint,
  GroupLinkageValue,
  HashedId8,
  LinkageValue,
  Opaque,
  SequenceOfPsidSsp,
  Signature,
  SubjectAssurance,
  GeographicRegion,
  Time32,
  Uint8,
  Uint16,
  Uint32
FROM IEEE1609dot2BaseTypes {iso(1) identified-organization(3) ieee(111)
    standards-association-numbered-series-standards(2) wave-stds(1609) dot2(2)
    base(1) base-types(2)}

  Certificate,
  CertificateType,
  Ieee1609Dot2Data,
  RecipientInfo,
  SignedData,
  SignerIdentifier,
  SymmetricCiphertext,
  ToBeSignedCertificate
FROM IEEE1609dot2 {iso(1) identified-organization(3) ieee(111)
    standards-association-numbered-series-standards(2) wave-stds(1609) dot2(2)
    base(1) schema(1)}

  EccP256PrivateKeyReconstruction,
  EncryptedIndividualPLV,
  EncryptedGroupPLV,
  IValue,
  LaHostnameId,
  RaHostnameId,
  PcaHostnameId,
  SecurityMgmtPsid
FROM Ieee1609dot2ScmsBaseTypes {iso(1) identified-organization(3) ieee(111)
    standards-association-numbered-series-standards(2) wave-stds(1609) dot2(2)
    scms(2) interfaces(1) base-types(2)}

  ScopedPcaRaError
FROM Ieee1609dot2ScmsError {iso(1) identified-organization(3) ieee(111)
    standards-association-numbered-series-standards(2) wave-stds(1609) dot2(2)
    scms(2) errors(2) complete(1)}

;

---
-- @brief The PcaRaInterfacePDU is the parent message type for messages sent between Pseudonym
--        Certificate Authority (PCA) and Registration Authority (RA).
-- @class PcaRaInterfacePDU
-- @param raPcaCertRequest  contains a message from an RA to the PCA to request a copy of the PCA’s
--                          currently valid certificate.
-- @param pcaRaCertResponse is a message from the PCA to the RA to acknowledge the receipt of
--                          raPcaCertRequest
PcaRaInterfacePDU::= CHOICE {
  raPcaCertRequest   RaPcaCertRequestMsg,
  pcaRaCertResponse  PcaRaCertResponseMsg,
  ...
}

---
-- @brief This data type is used by the RA to request pseudonym certificates from the PCA. It is
--        signed using the private key generated by the RA and the corresponding public key,
--        verificationKey, is placed for use by the PCA to generate the pseudonym certificates.
-- @class RaPcaCertRequestMsg 
-- @param version           contains the current version of the data type. The version specified in this
--                          document is version 1, represented by the integer 1.
-- @param raId              contains the RA's hostname.
-- @param cert-request-info contains the information to request certificates for OBEs. A
--                          PseudonymCertRequestInfo is included when the OBE requires pseudonimity
--                          and unlinkability. IdCertRequestInfo is included otherwise.
-- @see Uint8, RaHostnameId
RaPcaCertRequestMsg ::= SEQUENCE {
  version           Uint8(1),
  raId              RaHostnameId,
  cert-request-info CHOICE {
    pseudonym-cert-req     PseudonymCertRequestInfo,
    auth-cert-req          IdCertRequestInfo,
    ...
  }
}

---
-- @brief OBE Pseudonym Certificate info sent in the request certificate message. This version is only
--        for implicit certs using butterfly keys. If other versions of pseudonym cert requests are
--        developed with no butterfly keys or for explicit certs, that can be handled by defining an
--        additional CertRequestInfo type within RaPcaCertRequestMsg. In particular, this doesn't
--        allow pseudonym certs to have encryption keys, although it would in principle be possible to
--        support this if the CA added a value to the encryption key as well as modifying the signing
--        key. It's probably best for pseudonymous devices that want encrypted responses to do it via
--        a response encryption key in the SignedData anyway.
-- @class PseudonymCertRequestInfo 
-- @param psidSsp                   is a sequence of PSIDs with corresponding SSPs.
-- @param performanceAssuranceLevel indicates the assurance level of the certificate holder. This field is optional.
-- @param region                    defines the GeographicRegion for which a certificate is being
--                                  requested. This field is optional.
-- @param iValue                    denotes the week number from i=0 (i.e. 4:00 am Eastern Time on
--                                  Tuesday, January 6, 2015)
-- @param pca-id                    contains the PCA's hostname.
-- @param sig-butterfly-key-B       used to generate the hash of the pseudonym certificate request
--                                  from RA.
-- @param la1-id                    contains first LA's hostname (LA1).
-- @param la2-id                    contains second LA's hostname (LA2).
-- @param enc-plv1                  contains encrypted pre-linkage value received from LA1 for an
--                                  individual OBE.
-- @param enc-plv2                  contains encrypted pre-linkage value received from LA2 for an
--                                  individual OBE.
-- @param group-linkage-info        DEPRECATED: is a sequence containing linkage value information
--                                  of a group of OBEs. This field is optional.
-- @param enc-butterfly-key-H       contains RA's public key that is used by PCA to encrypt its responses.
-- @see SequenceOfPsidSsp, SubjectAssurance, GeographicRegion, IValue
PseudonymCertRequestInfo ::= SEQUENCE {
  --
  -- these fields go directly into the cert
  --
  psidSsp                           SequenceOfPsidSsp,
  performanceAssuranceLevel         SubjectAssurance OPTIONAL,
  region                            GeographicRegion OPTIONAL,
  iValue                            IValue,
  --
  -- used to create material that goes in the cert but not included in the
  -- cert directly
  --
  pca-id                 PcaHostnameId,
  sig-butterfly-key-B    EccP256CurvePoint,
  la1-id                 LaHostnameId,
  la2-id                 LaHostnameId,
  enc-plv1               EncryptedIndividualPLV,
  enc-plv2               EncryptedIndividualPLV,
  group-linkage-info     SEQUENCE {
      gla1-id                LaHostnameId,
      gla2-id                LaHostnameId,
      enc-gplv1              EncryptedGroupPLV,
      enc-gplv2              EncryptedGroupPLV
  } OPTIONAL,
  -- used to encrypt the response
  enc-butterfly-key-H    EccP256CurvePoint
}

---
-- @brief This structure defines the Identification Certificate information that is sent in the
--        request certificate message.
-- @class IdCertRequestInfo 
-- @param pca-id                  contains the PCA's hostname.
-- @param type                    contains the type information of certificate requested i.e. explicit
--                                certificate or implicit certificate.
-- @param to-be-signed-cert       is the certificate that is signed by PCA when it responds with a
--                                PcaRaCertResponseMsg. It contains the crlSeries (value inserted by
--                                PCA) and appPermissions (the Identification certificate request PSID)
--                                to be hashed when.
-- @param response-encryption-key is used by the PCA to encrypt the to-be-signed-cert.
-- @see PcaHostnameId, CertificateType, ToBeSignedCertificate, EccP256CurvePoint
IdCertRequestInfo ::= SEQUENCE {
  pca-id                 PcaHostnameId,
  type                   CertificateType,

  to-be-signed-cert   ToBeSignedCertificate(
    WITH COMPONENTS { ...,
      crlSeries(0),
      appPermissions
    }
  ),

  response-encryption-key EccP256CurvePoint
}


---
-- @brief This structure defines the response message to RaPcaCertRequestMsg. It is sent by PCA to RA.
-- @class PcaRaCertResponseMsg 
-- @param version     the current version of the data type. The version specified in this
--                    document is version 1, represented by the integer 1.
-- @param requestHash contains the hash of the original request, using the HashedId8 type as defined in
--                    1609dot2-base-types.asn of [2]. In the case when the PCA cannot calculate the
--                    hash of the original request due to a hardError, this field shall be all zeroes.
-- @param reply       contains the encrypted pseudonym certificates with corresponding linkage values
--                    for an individual OBE. A failure is sent if any form of error arises in
--                    communication between PCA and RA. Refer pca-ra-error.asn.
-- @see Uint8, HashedId8, PcaHostnameId, ScopedPcaRaError
PcaRaCertResponseMsg ::= SEQUENCE {
  version     Uint8(1),
  requestHash HashedId8,
  pca-id      PcaHostnameId,
  reply       CHOICE {
      success      CHOICE {
          signed-encrypted	SignedEncryptedCertificateResponse,
          raw               PlaintextCertificateResponse
      },
      failure ScopedPcaRaError
  },
  ...
}

---
-- @brief SignedEncrypted responses are signed 1609.2 data, containing encrypted 1609.2 data, which
--        decrypts to a DecryptedCertificateData containing the PlaintextCertificateResponse.
--
--        This is implemented as follows.

--        At the Signed level:
--        * ToBeSignedEncryptedCertificateResponse is defined with all the fields relevant to both
--          types of response plus optional i-value
--        * SignedEncryptedCertificateResponse is defined.

--        At the Encrypted level, the EncryptedCertificateData type is a 1609.2 data containing a
--        single recipient info which is encrypted to a response encryption key.

--        The EncryptedCertificateData decrypts to a DecryptedCertificateData, which is an unsecured
--        1609.2 data containing a PlaintextCertificateResponse. (It's a 1609.2 data to maintain
--        the convention that all EncryptedData decrypts to a 1609.2 data).

--        The PlaintextCertificateResponse distinguishes between: (implicit/explicit) and
--        (butterfly/single-key) as all four combinations are potentially legal and a receiver needs
--        to know which combination applies in order to recover the correct private key.
-- @class SignedEncryptedCertificateResponse 
-- @param unsecuredData contains the response that is signed by the PCA.
SignedEncryptedCertificateResponse ::= Ieee1609Dot2Data (WITH COMPONENTS {...,
  content (WITH COMPONENTS {
    signedData  (WITH COMPONENTS {...,
      tbsData (WITH COMPONENTS {
        payload (WITH COMPONENTS {...,
          data (WITH COMPONENTS {...,
             content (WITH COMPONENTS {
                unsecuredData (CONTAINING ToBeSignedEncryptedCertificateResponse)
            })
          }) PRESENT,
          extDataHash ABSENT
        }),
        headerInfo (WITH COMPONENTS {...,
          psid (SecurityMgmtPsid),
          generationTime ABSENT,
          expiryTime ABSENT,
          generationLocation ABSENT,
          p2pcdLearningRequest ABSENT,
          missingCrlIdentifier ABSENT,
          encryptionKey ABSENT
        })
      })
    })
  })
})

---
-- @brief Certificate response that is signed by the PCA while sending pseudonym certificates to RA.
-- @class ToBeSignedEncryptedCertificateResponse 
-- @param psidSsp        is a sequence of PSIDs and their corresponding SSPs.
-- @param expiration     indicates the expiration date of the certificate.
-- @param lifetime       indicates the time duration for which the certificate will be valid.
-- @param encrypted-data contains the Encrypted certificate sent from PCA to RA.
-- @see SequenceOfPsidSsp, Time32, Duration
ToBeSignedEncryptedCertificateResponse ::= SEQUENCE {
    psidSsp         SequenceOfPsidSsp,
    expiration      Time32,
    lifetime        Duration,
    encrypted-cert  EncryptedCertificateData
}

---
-- @brief This structure encloses the encrypted certificate data that decrypts to a
--        DecryptedCertificateData by the EE.
-- @class EncryptedCertificateData 
EncryptedCertificateData ::= Ieee1609Dot2Data (WITH COMPONENTS {
  content (WITH COMPONENTS {...,
    encryptedData (WITH COMPONENTS {
      ...,
      recipients (SIZE(1) INTERSECTION (WITH COMPONENT (
        RecipientInfo (WITH COMPONENTS {rekRecipInfo})
      )))
    })
  })
})

---
-- @brief This structure contains the certificate data in plain text which is obtained by the EE by
--        decrypting EncryptedCertificateData.
-- @class DecryptedCertificateData 
DecryptedCertificateData ::= Ieee1609Dot2Data (WITH COMPONENTS {
    content (WITH COMPONENTS {...,
      unsecuredData (CONTAINING PlaintextCertificateResponse
    )
  })
})

---
-- @brief This structure contains the certificate data created by the PCA.
-- @class PlaintextCertificateResponse 
-- @param implicit-butterfly denotes the butterfly key included in this structure when certificate
--                           sent by the PCA is of implicit type.
-- @param implicit           is the implicit certificate produced by the PCA.
-- @param explicit-butterfly denotes the butterfly key included in this structure when certiciate
--                           sent by the PCA is of explicit type.
-- @param explicit           is the explicit certificate produced by the PCA.
PlaintextCertificateResponse ::= CHOICE {
    implicit-butterfly   ImplicitCertResponse,
    implicit             ImplicitCertResponse,
    explicit-butterfly   ButterflyExplicitCertResponse,
    explicit             Certificate
}

---
-- @brief This structure defines the implicit certificate type which is sent as a response to an EE.
-- @class ImplicitCertResponse 
-- @param certificate is the implicit certificate produced by the PCA.
-- @param priv-key-reconstruction-s is the value required to reconstruct the PCA's public key.
ImplicitCertResponse ::= SEQUENCE {
    certificate             Certificate (WITH COMPONENTS { ...,
        type(implicit),
        issuer(WITH COMPONENTS {sha256AndDigest})
    }),
    priv-key-reconstruction-s EccP256PrivateKeyReconstruction
}

---
-- @brief This structure defines the explicit certificate type which is sent as a response to an EE.
-- @class ButterflyExplicitCertResponse 
-- @param certificate is the explicit certificate produced by the PCA.
-- @param priv-key-reconstruction-s NOTE that this is actually a randomization value used by an EE
--                                  to reconstruct the PCA's public key.
ButterflyExplicitCertResponse ::= SEQUENCE {
    certificate             Certificate (WITH COMPONENTS { ...,
        type(explicit),
        issuer(WITH COMPONENTS {sha256AndDigest})
    }),
    priv-key-reconstruction-c EccP256PrivateKeyReconstruction
}

END
