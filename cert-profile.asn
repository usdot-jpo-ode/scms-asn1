-- 
--  Copyright 2017 Crash Avoidance Metrics Partner, VSC5 Consortium
-- 
--  Licensed under the Apache License, Version 2.0 (the "License");
--  you may not use this file except in compliance with the License.
--  You may obtain a copy of the License at
-- 
--     http://www.apache.org/licenses/LICENSE-2.0
-- 
--  Unless required by applicable law or agreed to in writing, software
--  distributed under the License is distributed on an "AS IS" BASIS,
--  WITHOUT WARRANTIES OR CONDITIONS OF ANY KIND, either express or implied.
--  See the License for the specific language governing permissions and
--  limitations under the License.
-- 
-- @namespace IEEE1609dot2-profiles
IEEE1609dot2-profiles {iso(1) identified-organization(3) ieee(111) 
standards-association-numbered-series-standards(2) wave-stds(1609)  
dot2(2) base (1) profiles (3)}

DEFINITIONS AUTOMATIC TAGS ::= BEGIN

EXPORTS ALL;

IMPORTS 
  Certificate,
  Countersignature,
  ExplicitCertificate, 
  ImplicitCertificate,
  PsidGroupPermissions,
  PsidSsp,
  SequenceOfPsidGroupPermissions,
  SequenceOfPsidSsp,
  SequenceOfPsidSspRange
FROM IEEE1609dot2 {iso(1) identified-organization(3) ieee(111) 
    standards-association-numbered-series-standards(2) wave-stds(1609)  
    dot2(2) base(1) schema(1)}

  CrlSeries,
  IdentifiedRegion,
  Psid,
  PsidSspRange,
  SequenceOfIdentifiedRegion
FROM IEEE1609dot2BaseTypes {iso(1) identified-organization(3) ieee(111) 
standards-association-numbered-series-standards(2) wave-stds(1609)  
dot2(2) base(1) base-types(2)}

  CrlPsid -- PSID = 0x100
FROM IEEE1609dot2Crl {iso(1) identified-organization(3) ieee(111) 
  standards-association-numbered-series-standards(2) wave-stds(1609)  
  dot2(2) crl(3) protocol(2)}

  CrlSsp,
  PermissibleCrls
FROM IEEE1609dot2CrlSsp {iso(1) identified-organization(3) ieee(111) 
    standards-association-numbered-series-standards(2) wave-stds(1609)  
    dot2(2) crl(3) service-specific-permissions (3)}

  Canada,
  Mexico,
  USA,

  CrlgCertExpiration,
  DcmCertExpiration,
  EcaCertExpirationCvp,
  EcaCertExpirationPoc,
  ElectorCertExpiration,
  IcaCertExpirationCvp,
  IcaCertExpirationPoc,
  LaCertExpiration,
  MaCertExpiration,
  ObeEnrollmentCertExpirationCvp,
  ObeEnrollmentCertExpirationPoc,
  ObeIdentificationCertExpiration,
  ObePseudonymCertExpiration,
  PcaCertExpiration,
  PgCertExpiration,
  RaCertExpiration,
  RootCaCertExpiration,
  RseApplicationCertExpiration,
  RseEnrollmentCertExpirationCvp,
  RseEnrollmentCertExpirationPoc,
  
  BsmPsid, --PSID = 0x20
  SecurityMgmtPsid,  -- PSID = 0x23
  MisbehaviorReportingPsid,  -- PSID = 0x26
  VulnerableRoadUsersSafetyPsid, -- PSID = 0x27
  DifferentialGpsCorrectionsUncompressedPsid, -- PSID = 0x80
  DifferentialGpsCorrectionsCompressedPsid, -- PSID = 0x81
  IntersectionSafetyAndAwarenessPsid, -- PSID = 0x82
  TravellerInformationAndRoadsideSignagePsid, -- PSID = 0x83
  WaveServiceAdvertisementPsid, -- PSID = 0x87
  VehicleInitiatedDistressNotificationPsid, -- PSID = 0x4082
  TranscoreSoftwareUpdatePsid, -- PSID = 0x204083
  CVPApplication1Psid, -- PSID = 0x204088
  CVPApplication2Psid, -- PSID = 0x204089
  CVPApplication3Psid, -- PSID = 0x20408A
  CVPApplication4Psid, -- PSID = 0x20408B
  CVPApplication5Psid, -- PSID = 0x20408C
  CVPApplication6Psid, -- PSID = 0x20408D
  CVPApplication7Psid, -- PSID = 0x20408E
  CVPApplication8Psid, -- PSID = 0x20408F
  CVPApplication9Psid, -- PSID = 0x204090
  CVPApplication10Psid, -- PSID = 0x204091
  CVPApplication11Psid, -- PSID = 0x204092
  CVPApplication12Psid, -- PSID = 0x204093
  CVPApplication13Psid, -- PSID = 0x204094
  CVPApplication14Psid, -- PSID = 0x204095
  CVPApplication15Psid, -- PSID = 0x204096
  CVPApplication16Psid, -- PSID = 0x204097
  
  EeEnrollmentCrlSeries,
  EeNonPseudonymCrlSeries,
  ObePseudonymCrlSeries,
  ScmsComponentCrlSeries,
  ScmsSpclComponentCrlSeries
FROM Ieee1609dot2ScmsBaseTypes {iso(1) identified-organization(3) ieee(111)
standards-association-numbered-series-standards(2) wave-stds(1609)  dot2(2)
scms (2) interfaces(1) base-types (2)}
;


---
-- @brief This data type defines the CRL generator's certificate structure and 
--        its contents generated by the Root CA. The CRL generator does not
--        provide a public key (encryptionKey) for encryption of data sent by
--        other components in the SCMS ecosystem.
-- @class CrlgCertificate
-- @param issuer     contains the hash of the certificate contents generated by
--                   the Root CA.
-- @param toBeSigned contains certificate content that is signed by the CRL
--                   generator.
-- @see IssuerIdentifier
CrlgCertificate ::= ExplicitCertificate (WITH COMPONENTS { ...,
  issuer (WITH COMPONENTS {sha256AndDigest}),
  toBeSigned (WITH COMPONENTS { ...,
    id (WITH COMPONENTS {
      name ("crlg.v2xscms.com" | "crlg.cvp.v2xscms.com") -- !!TBD!!
    }),
    cracaId, --set to HashedId3 of the Root CA cert
    crlSeries(ScmsSpclComponentCrlSeries),
    validityPeriod (WITH COMPONENTS { ...,
      duration (CrlgCertExpiration)
    }),
    region ABSENT,
    assuranceLevel ABSENT,
    appPermissions (SequenceOfPsidSsp (SIZE(2)) (CONSTRAINED BY {
      PsidSsp (WITH COMPONENTS {
        psid (SecurityMgmtPsid), -- PSID = 0x23
        ssp --OER encoding of ScmsSsp indicating CrlSignerSsp
      }),
      PsidSsp (WITH COMPONENTS {
        psid (CrlPsid), -- PSID = 0x100
        ssp (WITH COMPONENTS {opaque(CONTAINING CrlSsp (WITH COMPONENTS {..., 
          associatedCraca(issuerIsCraca),
          crls (PermissibleCrls (SIZE(4)) (CONSTRAINED BY {
            CrlSeries (EeEnrollmentCrlSeries),
            CrlSeries (EeNonPseudonymCrlSeries),
            CrlSeries (ObePseudonymCrlSeries),
            CrlSeries (ScmsComponentCrlSeries)
          }))
        }))})
      })
    })),
    certIssuePermissions ABSENT,
    certRequestPermissions ABSENT,
    canRequestRollover (NULL),
    encryptionKey ABSENT,
    verifyKeyIndicator (WITH COMPONENTS {
      verificationKey (WITH COMPONENTS {
        ecdsaNistP256 (WITH COMPONENTS {
          compressed-y-0, compressed-y-1
        })
      })
    })
  })
})

---
-- @brief This data type defines the Device Configuration Manager's (DCM)
--        certificate structure and its contents generated by ???. DCM provides
--        a public key (encryptionKey) so that other SCMS components can send 
--        data securely to the DCM.
-- @class DcmCertificate
-- @param issuer     contains the hash of the certificate contents generated by
--                   the ???.
-- @param toBeSigned contains certificate content that is signed by the DCM
--                   generator.
-- @see IssuerIdentifier
DcmCertificate ::= ExplicitCertificate (WITH COMPONENTS { ...,
  issuer (WITH COMPONENTS{sha256AndDigest}),
  toBeSigned (WITH COMPONENTS { ...,
    id (WITH COMPONENTS {
      name ("dcm.v2xscms.com" | "v2v-dcm.cvp.v2xscms.com" | "v2i-dcm.cvp.v2xscms.com") -- !!TBD!!
    }),
    cracaId, --set to HashedId3 of the Root CA cert
    crlSeries(ScmsComponentCrlSeries),
    validityPeriod (WITH COMPONENTS { ...,
      duration (DcmCertExpiration)
    }),
    region (WITH COMPONENTS {
      identifiedRegion (SequenceOfIdentifiedRegion (SIZE(1)) (CONSTRAINED BY {
        IdentifiedRegion ( WITH COMPONENTS { countryOnly(USA) })
      }))
    }),
    assuranceLevel ABSENT,
    appPermissions (SequenceOfPsidSsp (SIZE(1)) (CONSTRAINED BY {
      PsidSsp (WITH COMPONENTS {
        psid (SecurityMgmtPsid), -- PSID = 0x23
        ssp --OER encoding of ScmsSsp indicating Dcmssp
      })
    })),
    certIssuePermissions ABSENT,
    certRequestPermissions (SequenceOfPsidGroupPermissions (SIZE(1)) (CONSTRAINED BY {
      PsidGroupPermissions ( WITH COMPONENTS {..., 
	    subjectPermissions (WITH COMPONENTS { 
          explicit (SequenceOfPsidSspRange (SIZE (2)) (CONSTRAINED BY {
		    PsidSspRange (WITH COMPONENTS {
			  psid (BsmPsid), --PSID = 0x20
              sspRange(WITH COMPONENTS{ 
                opaque -- single OCTET STRING of length 0  
              }) 
		    }),
		    PsidSspRange (WITH COMPONENTS {
			  psid (MisbehaviorReportingPsid), -- PSID = 0x26
              sspRange ABSENT 
		    })
          }))
        }),
        minChainDepth(0), chainDepthRange(0),
        eeType({enrol})
      })
    })),
    canRequestRollover(NULL),
    encryptionKey PRESENT,
    verifyKeyIndicator (WITH COMPONENTS {
      verificationKey (WITH COMPONENTS {
        ecdsaNistP256 (WITH COMPONENTS {
          compressed-y-0, compressed-y-1
        })
      })
    })
  })
})


---
-- @brief This data type defines an Elector's certificate structure and its 
--        contents generated by the SCMS Manager. An Elector does not provide 
--        a public key (encryptionKey).
-- @class ElectorCertificate
-- @param issuer     contains the hash of the certificate contents generated by
--                   the SCMS Manager.
-- @param toBeSigned contains certificate content that is signed by the CRL
--                   generator.
-- @see IssuerIdentifier
ElectorCertificate ::= ExplicitCertificate (WITH COMPONENTS { ...,
  issuer (WITH COMPONENTS {self}),
  toBeSigned (WITH COMPONENTS { ...,
    id (WITH COMPONENTS {
      name ("") -- !!TBD!!
    }),
    cracaId('000000'H),
    crlSeries(0),                          
    validityPeriod (WITH COMPONENTS { ...,
      duration (ElectorCertExpiration)
    }),
    region ABSENT,
    assuranceLevel ABSENT,
    appPermissions (SequenceOfPsidSsp (SIZE(1)) (CONSTRAINED BY {
      PsidSsp (WITH COMPONENTS {
        psid (SecurityMgmtPsid), -- PSID = 0x23
        ssp --OER encoding of ScmsSsp indicating ElectorSsp
      })
    })),
    certIssuePermissions ABSENT,
    certRequestPermissions ABSENT,
    canRequestRollover ABSENT,
    encryptionKey ABSENT,
    verifyKeyIndicator (WITH COMPONENTS {
      verificationKey (WITH COMPONENTS {
        ecdsaNistP256 (WITH COMPONENTS {
          compressed-y-0, compressed-y-1
        })
      })
    })
  })
})

---
-- @brief This data type defines an Enrollment Certificate Authority's (ECA) 
--        certificate structure and its contents generated by the Intermediate 
--        Certificate Authority (ICA). The ECA provides a public key (
--        encryptionKey) so that other SCMS components can send data securely
--        to this ECA.
-- @class EcaCertificate
-- @param issuer     contains the hash of the certificate contents generated by
--                   the ICA.
-- @param toBeSigned contains certificate content that is signed by the ECA.
-- @see IssuerIdentifier
EcaCertificate ::= ExplicitCertificate (WITH COMPONENTS { ...,
  issuer (WITH COMPONENTS {sha256AndDigest}),
  toBeSigned (WITH COMPONENTS { ...,
    id (WITH COMPONENTS {
      name ("eca.prod.v2xscms.com" | "eca.qa.v2xscms.com" | "eca.test.v2xscms.com")
    }),
    cracaId, --set to HashedId3 of the Root CA cert
    crlSeries(ScmsComponentCrlSeries),
    validityPeriod (WITH COMPONENTS { ...,
      duration (EcaCertExpirationPoc | EcaCertExpirationCvp)
    }),
    region (WITH COMPONENTS {
      identifiedRegion (SequenceOfIdentifiedRegion (SIZE(1)) (CONSTRAINED BY {
        IdentifiedRegion ( WITH COMPONENTS { countryOnly(USA) })
      }))
    }),
    assuranceLevel ABSENT,
    appPermissions (SequenceOfPsidSsp (SIZE(1)) (CONSTRAINED BY {
      PsidSsp (WITH COMPONENTS {
        psid (SecurityMgmtPsid), -- PSID = 0x23
        ssp --OER encoding of ScmsSsp indicating Ecassp
      })
    })),
    certIssuePermissions (SequenceOfPsidGroupPermissions (SIZE (1)) (WITH COMPONENT (WITH COMPONENTS {..., 
	  subjectPermissions (WITH COMPONENTS {..., 
		explicit (SequenceOfPsidSspRange (SIZE (26)) (CONSTRAINED BY{
		  PsidSspRange (WITH COMPONENTS {
			psid (BsmPsid), --PSID = 0x20
            sspRange(WITH COMPONENTS{ 
              opaque -- single OCTET STRING of length 0  
            }) 
		  }),
          PsidSspRange (WITH COMPONENTS {
			psid (MisbehaviorReportingPsid), -- PSID = 0x26
            sspRange ABSENT 
		  }),
          PsidSspRange (WITH COMPONENTS {
			psid (VulnerableRoadUsersSafetyPsid), -- PSID = 0x27
            sspRange ABSENT 
		  }),
          PsidSspRange (WITH COMPONENTS {
			psid (DifferentialGpsCorrectionsUncompressedPsid), -- PSID = 0x80 
            sspRange ABSENT 
		  }),
          PsidSspRange (WITH COMPONENTS {
			psid (DifferentialGpsCorrectionsCompressedPsid), -- PSID = 0x81 
            sspRange ABSENT 
		  }),
          PsidSspRange (WITH COMPONENTS {
			psid (IntersectionSafetyAndAwarenessPsid), -- PSID = 0x82 
            sspRange(WITH COMPONENTS{
              opaque --SSP: 90-01, 90-FF-FF-01, 90-FF-FF-02, 90-FF-FF-03, 90-FF-FF-04  
            }) 
		  }),
          PsidSspRange (WITH COMPONENTS {
			psid (TravellerInformationAndRoadsideSignagePsid), -- PSID = 0x83 
            sspRange ABSENT 
		  }),
          PsidSspRange (WITH COMPONENTS {
			psid (WaveServiceAdvertisementPsid), -- PSID = 0x87 
            sspRange(WITH COMPONENTS{
              opaque -- single OCTET STRING of length 0 
            }) 
		  }),
          PsidSspRange (WITH COMPONENTS {
			psid (VehicleInitiatedDistressNotificationPsid), -- PSID = 0x4082
            sspRange ABSENT 
		  }),
          PsidSspRange (WITH COMPONENTS {
			psid (TranscoreSoftwareUpdatePsid), -- PSID = 0x204083
            sspRange ABSENT 
		  }),
          PsidSspRange (WITH COMPONENTS {
			psid (CVPApplication1Psid), -- PSID = 0x204088
            sspRange ABSENT 
		  }),
          PsidSspRange (WITH COMPONENTS {
			psid (CVPApplication2Psid), -- PSID = 0x204089
            sspRange ABSENT 
		  }),
          PsidSspRange (WITH COMPONENTS {
			psid (CVPApplication3Psid), -- PSID = 0x20408A
            sspRange ABSENT 
		  }),
          PsidSspRange (WITH COMPONENTS {
			psid (CVPApplication4Psid), -- PSID = 0x20408B
            sspRange ABSENT 
		  }),
          PsidSspRange (WITH COMPONENTS {
			psid (CVPApplication5Psid), -- PSID = 0x20408C
            sspRange ABSENT 
		  }),
          PsidSspRange (WITH COMPONENTS {
			psid (CVPApplication6Psid), -- PSID = 0x20408D
            sspRange ABSENT 
		  }),
          PsidSspRange (WITH COMPONENTS {
			psid (CVPApplication7Psid), -- PSID = 0x20408E
            sspRange ABSENT 
		  }),
          PsidSspRange (WITH COMPONENTS {
			psid (CVPApplication8Psid), -- PSID = 0x20408F
            sspRange ABSENT 
		  }),
          PsidSspRange (WITH COMPONENTS {
			psid (CVPApplication9Psid), -- PSID = 0x204090
            sspRange ABSENT 
		  }),
          PsidSspRange (WITH COMPONENTS {
			psid (CVPApplication10Psid), -- PSID = 0x204091
            sspRange ABSENT 
		  }),
          PsidSspRange (WITH COMPONENTS {
			psid (CVPApplication11Psid), -- PSID = 0x204092
            sspRange ABSENT 
		  }),
          PsidSspRange (WITH COMPONENTS {
			psid (CVPApplication12Psid), -- PSID = 0x204093
            sspRange ABSENT 
		  }),
          PsidSspRange (WITH COMPONENTS {
			psid (CVPApplication13Psid), -- PSID = 0x204094
            sspRange ABSENT 
		  }),
          PsidSspRange (WITH COMPONENTS {
			psid (CVPApplication14Psid), -- PSID = 0x204095
            sspRange ABSENT 
		  }),
          PsidSspRange (WITH COMPONENTS {
			psid (CVPApplication15Psid), -- PSID = 0x204096
            sspRange ABSENT 
		  }),
          PsidSspRange (WITH COMPONENTS {
			psid (CVPApplication16Psid), -- PSID = 0x204097
            sspRange ABSENT 
		  })
		}))
	  }),
	  minChainDepth(1), chainDepthRange(0),
      eeType({enrol})
    }))),
    certRequestPermissions ABSENT,
    canRequestRollover (NULL),
    encryptionKey PRESENT,
    verifyKeyIndicator (WITH COMPONENTS {
      verificationKey (WITH COMPONENTS {
        ecdsaNistP256 (WITH COMPONENTS {
          compressed-y-0, compressed-y-1
        })
      })
    })
  })
})

---
-- @brief This data type defines an Intermediate Certificate Authority's (ICA) 
--        certificate structure and its contents. An ICA certificate can be 
--        generated by another ICA. The ICA does not provide a public key
--        (encryptionKey).
-- @class IcaCertificate
-- @param issuer     contains the hash of the certificate contents generated by
--                   the ICA.
-- @param toBeSigned contains certificate content that is signed by the ICA.
-- @see IssuerIdentifier
IcaCertificate ::= ExplicitCertificate (WITH COMPONENTS { ...,
  issuer (WITH COMPONENTS {sha256AndDigest}),
  toBeSigned (WITH COMPONENTS { ...,
    id (WITH COMPONENTS {
      name ("ica.prod.v2xscms.com" | "ica.qa.v2xscms.com" | "ica.test.v2xscms.com")
    }),
    cracaId, --set to HashedId3 of the Root CA cert
    crlSeries(ScmsComponentCrlSeries),
    validityPeriod (WITH COMPONENTS { ...,
      duration (IcaCertExpirationPoc | IcaCertExpirationCvp)
    }),
    region (WITH COMPONENTS {
      identifiedRegion (SequenceOfIdentifiedRegion (SIZE(1)) (CONSTRAINED BY {
        IdentifiedRegion ( WITH COMPONENTS { countryOnly(USA) })
      }))
    }),
    assuranceLevel ABSENT,
    appPermissions (SequenceOfPsidSsp (SIZE(1)) (CONSTRAINED BY {
      PsidSsp (WITH COMPONENTS {
        psid (SecurityMgmtPsid), -- PSID = 0x23
        ssp --OER encoding of ScmsSsp indicating Icassp
      })
    })),
    certIssuePermissions (SequenceOfPsidGroupPermissions (SIZE(2)) (CONSTRAINED BY {
      PsidGroupPermissions ( WITH COMPONENTS {..., 
	    subjectPermissions (WITH COMPONENTS { 
          all
        }),
        minChainDepth(2), chainDepthRange(0),
	    eeType ({app, enrol})
      }),
      PsidGroupPermissions ( WITH COMPONENTS {..., 
        subjectPermissions (WITH COMPONENTS { 
          explicit (SequenceOfPsidSspRange (SIZE (26)) (CONSTRAINED BY{
          PsidSspRange (WITH COMPONENTS {
            psid (BsmPsid), --PSID = 0x20
            sspRange(WITH COMPONENTS{ 
              opaque -- single OCTET STRING of length 0  
            }) 
          }),
          PsidSspRange (WITH COMPONENTS {
            psid (MisbehaviorReportingPsid), -- PSID = 0x26
            sspRange ABSENT 
          }),
          PsidSspRange (WITH COMPONENTS {
            psid (VulnerableRoadUsersSafetyPsid), -- PSID = 0x27
            sspRange ABSENT 
          }),
          PsidSspRange (WITH COMPONENTS {
            psid (DifferentialGpsCorrectionsUncompressedPsid), -- PSID = 0x80 
            sspRange ABSENT 
          }),
          PsidSspRange (WITH COMPONENTS {
            psid (DifferentialGpsCorrectionsCompressedPsid), -- PSID = 0x81 
            sspRange ABSENT 
          }),
          PsidSspRange (WITH COMPONENTS {
            psid (IntersectionSafetyAndAwarenessPsid), -- PSID = 0x82 
            sspRange(WITH COMPONENTS{
              opaque --SSP: 90-01, 90-FF-FF-01, 90-FF-FF-02, 90-FF-FF-03, 90-FF-FF-04  
            }) 
          }),
          PsidSspRange (WITH COMPONENTS {
            psid (TravellerInformationAndRoadsideSignagePsid), -- PSID = 0x83 
            sspRange ABSENT 
          }),
          PsidSspRange (WITH COMPONENTS {
            psid (WaveServiceAdvertisementPsid), -- PSID = 0x87 
            sspRange(WITH COMPONENTS{
              opaque -- single OCTET STRING of length 0 
            }) 
          }),
          PsidSspRange (WITH COMPONENTS {
            psid (VehicleInitiatedDistressNotificationPsid), -- PSID = 0x4082
            sspRange ABSENT 
          }),
          PsidSspRange (WITH COMPONENTS {
            psid (TranscoreSoftwareUpdatePsid), -- PSID = 0x204083
            sspRange ABSENT 
          }),
          PsidSspRange (WITH COMPONENTS {
            psid (CVPApplication1Psid), -- PSID = 0x204088
            sspRange ABSENT 
          }),
          PsidSspRange (WITH COMPONENTS {
            psid (CVPApplication2Psid), -- PSID = 0x204089
            sspRange ABSENT 
          }),
          PsidSspRange (WITH COMPONENTS {
            psid (CVPApplication3Psid), -- PSID = 0x20408A
            sspRange ABSENT 
          }),
          PsidSspRange (WITH COMPONENTS {
            psid (CVPApplication4Psid), -- PSID = 0x20408B
            sspRange ABSENT 
          }),
          PsidSspRange (WITH COMPONENTS {
            psid (CVPApplication5Psid), -- PSID = 0x20408C
            sspRange ABSENT 
          }),
          PsidSspRange (WITH COMPONENTS {
            psid (CVPApplication6Psid), -- PSID = 0x20408D
            sspRange ABSENT 
          }),
          PsidSspRange (WITH COMPONENTS {
            psid (CVPApplication7Psid), -- PSID = 0x20408E
            sspRange ABSENT 
          }),
          PsidSspRange (WITH COMPONENTS {
            psid (CVPApplication8Psid), -- PSID = 0x20408F
            sspRange ABSENT 
          }),
          PsidSspRange (WITH COMPONENTS {
            psid (CVPApplication9Psid), -- PSID = 0x204090
            sspRange ABSENT 
          }),
          PsidSspRange (WITH COMPONENTS {
            psid (CVPApplication10Psid), -- PSID = 0x204091
            sspRange ABSENT 
          }),
          PsidSspRange (WITH COMPONENTS {
            psid (CVPApplication11Psid), -- PSID = 0x204092
            sspRange ABSENT 
          }),
          PsidSspRange (WITH COMPONENTS {
            psid (CVPApplication12Psid), -- PSID = 0x204093
            sspRange ABSENT 
          }),
          PsidSspRange (WITH COMPONENTS {
            psid (CVPApplication13Psid), -- PSID = 0x204094
            sspRange ABSENT 
          }),
          PsidSspRange (WITH COMPONENTS {
            psid (CVPApplication14Psid), -- PSID = 0x204095
            sspRange ABSENT 
          }),
          PsidSspRange (WITH COMPONENTS {
            psid (CVPApplication15Psid), -- PSID = 0x204096
            sspRange ABSENT 
          }),
          PsidSspRange (WITH COMPONENTS {
            psid (CVPApplication16Psid), -- PSID = 0x204097
            sspRange ABSENT 
          })
        }))
        }),
        minChainDepth(1), chainDepthRange(-1),
        eeType ({app, enrol})
      })
    })),
    certRequestPermissions ABSENT,
    canRequestRollover (NULL),
    encryptionKey ABSENT,
    verifyKeyIndicator (WITH COMPONENTS {
      verificationKey (WITH COMPONENTS {
        ecdsaNistP256 (WITH COMPONENTS {
          compressed-y-0, compressed-y-1
        })
      })
    })
  })
})

---
-- @brief This data type defines a Linkage Authority's (LA) certificate 
--        structure and its contents generated by the Intermediate Certificate 
--        Authority (ICA). The LA does not provide a public key (encryptionKey)
--        for secure communication. Instead it uses shared symmetric key
--        encryption for secure communication with the PCA.
-- @class LaCertificate
-- @param issuer     contains the hash of the certificate contents generated by
--                   the ICA.
-- @param toBeSigned contains certificate content that is signed by the LA.
-- @see IssuerIdentifier
LaCertificate ::= ExplicitCertificate (WITH COMPONENTS { ...,
  issuer (WITH COMPONENTS{sha256AndDigest}),
  toBeSigned (WITH COMPONENTS { ...,
    id (WITH COMPONENTS {
      name ("la1.prod.v2xscms.com" | "la2.prod.v2xscms.com" | "la1.qa.v2xscms.com" | "la2.qa.v2xscms.com" | "la1.test.v2xscms.com" | "la2.test.v2xscms.com")
    }),
    cracaId, --set to HashedId3 of the Root CA cert
    crlSeries(ScmsComponentCrlSeries),
    validityPeriod (WITH COMPONENTS { ...,
      duration (LaCertExpiration)
    }),
    region (WITH COMPONENTS {
      identifiedRegion (SequenceOfIdentifiedRegion (SIZE(1)) (CONSTRAINED BY {
        IdentifiedRegion ( WITH COMPONENTS { countryOnly(USA) })
      }))
    }),
    assuranceLevel ABSENT,
    appPermissions (SequenceOfPsidSsp (SIZE(1)) (CONSTRAINED BY {
      PsidSsp (WITH COMPONENTS {
        psid (SecurityMgmtPsid), -- PSID = 0x23
        ssp --OER encoding of ScmsSsp indicating Lassp
      })
    })),
    certIssuePermissions ABSENT,
    certRequestPermissions ABSENT,
    canRequestRollover (NULL),
    encryptionKey ABSENT,
    verifyKeyIndicator (WITH COMPONENTS {
      verificationKey (WITH COMPONENTS {
        ecdsaNistP256 (WITH COMPONENTS {
          compressed-y-0, compressed-y-1
        })
      })
    })
  })
})

---
-- @brief This data type defines a Misbehavior Authority's (MA) certificate 
--        structure and its contents. The MA provides a public key
--        (encryptionKey) so that other SCMS components can send data securely 
--        to this MA.
-- @class MaCertificate
-- @param issuer     contains the hash of the certificate contents.
-- @param toBeSigned contains certificate content that is signed by the MA.
-- @see IssuerIdentifier
MaCertificate ::= ExplicitCertificate (WITH COMPONENTS { ...,
  issuer (WITH COMPONENTS {sha256AndDigest}),
  toBeSigned (WITH COMPONENTS { ...,
    id (WITH COMPONENTS {
      name ("ma.prod.v2xscms.com" | "ma.qa.v2xscms.com" | "ma.test.v2xscms.com")
    }),
    cracaId, --set to HashedId3 of the Root CA cert
    crlSeries(ScmsSpclComponentCrlSeries),
    validityPeriod (WITH COMPONENTS { ...,
      duration (MaCertExpiration)
    }),
    region ABSENT,
    assuranceLevel ABSENT,
    appPermissions (SequenceOfPsidSsp (SIZE(1)) (CONSTRAINED BY {
      PsidSsp (WITH COMPONENTS {
        psid (SecurityMgmtPsid), -- PSID = 0x23
        ssp ABSENT --TBD in the MBD project. It is ABSENT only for POC.
      })
    })),
    certIssuePermissions ABSENT,
    certRequestPermissions ABSENT,
    canRequestRollover (NULL),
    encryptionKey PRESENT,
    verifyKeyIndicator (WITH COMPONENTS {
      verificationKey (WITH COMPONENTS {
        ecdsaNistP256 (WITH COMPONENTS {
          compressed-y-0, compressed-y-1
        })
      })
    })
  })
})

---
-- @brief This data type defines an On-Board Equipment's (OBE) enrollment 
--        certificate structure and its contents. The ECA provides this
--        certificate on request from the DCM while bootstrapping the device.
-- @class ObeEnrollmentCertificate
-- @param issuer     contains the hash of the certificate contents.
-- @param toBeSigned contains certificate content that is signed by the OBE.
-- @see IssuerIdentifier
ObeEnrollmentCertificate ::= ImplicitCertificate (WITH COMPONENTS { ...,
  issuer (WITH COMPONENTS{sha256AndDigest}),
  toBeSigned (WITH COMPONENTS { ...,
    id (WITH COMPONENTS { 
      name("")
    }),
    cracaId, --set to HashedId3 of the Root CA cert
    crlSeries(EeEnrollmentCrlSeries),
    validityPeriod (WITH COMPONENTS { ...,
      duration (ObeEnrollmentCertExpirationPoc | ObeEnrollmentCertExpirationCvp)
    }),
    region (WITH COMPONENTS {
      identifiedRegion (SequenceOfIdentifiedRegion (SIZE(1)) (CONSTRAINED BY {
        IdentifiedRegion ( WITH COMPONENTS { countryOnly(USA) })
      }))
    }),
    assuranceLevel ABSENT,
    appPermissions ABSENT,
    certIssuePermissions ABSENT,
    certRequestPermissions (SequenceOfPsidGroupPermissions (SIZE(1)) (CONSTRAINED BY { --THIS MAY CHANGE AS SPECIFIED BY SCMS MANAGER
      PsidGroupPermissions ( WITH COMPONENTS {..., 
	    subjectPermissions (WITH COMPONENTS { 
          explicit (SequenceOfPsidSspRange (SIZE (2)) (CONSTRAINED BY {
		    PsidSspRange (WITH COMPONENTS {
			  psid (BsmPsid), --PSID = 0x20
              sspRange(WITH COMPONENTS{ 
                opaque -- single OCTET STRING of length 0  
              }) 
		    }),
		    PsidSspRange (WITH COMPONENTS {
			  psid (MisbehaviorReportingPsid), -- PSID = 0x26
              sspRange(WITH COMPONENTS{ 
                opaque -- single OCTET STRING of length 0  
              }) 
		    })
          }))
        }),
        minChainDepth(0), chainDepthRange(0),
        eeType({app})
      })
    })),
    canRequestRollover(NULL),
    encryptionKey ABSENT,
    verifyKeyIndicator (WITH COMPONENTS {
      reconstructionValue (WITH COMPONENTS {
        compressed-y-0, compressed-y-1
      })
    })
  })
})

---
-- @brief This data type defines an On-Board Equipment's (OBE) identifcation
--        certificate structure and its contents. The RA brokers the
--        communication for provisioning this certificate from PCA to the OBE.
-- @class ObeIdentificationCertificate
-- @param issuer     contains the hash of the certificate contents.
-- @param toBeSigned contains certificate content that is signed by the OBE.
-- @see IssuerIdentifier
ObeIdentificationCertificate ::= ImplicitCertificate (WITH COMPONENTS { ...,
  issuer (WITH COMPONENTS {sha256AndDigest}),
    toBeSigned (WITH COMPONENTS { ...,
      id (WITH COMPONENTS {
        binaryId (SIZE (8))  -- RIF value shall be used as the certificate ID
      }),
    cracaId, --set to HashedId3 of the Root CA cert
    crlSeries(EeNonPseudonymCrlSeries),
    validityPeriod (WITH COMPONENTS { ...,
      duration (ObeIdentificationCertExpiration)
    }),
    region (WITH COMPONENTS {
      identifiedRegion (SequenceOfIdentifiedRegion (SIZE(1)) (CONSTRAINED BY {
        IdentifiedRegion ( WITH COMPONENTS { countryOnly(USA) })
      }))
    }),
    assuranceLevel ABSENT,
    --appPermissions TO BE SPECIFIED BY SCMS MANAGER,
    certIssuePermissions ABSENT,
    certRequestPermissions ABSENT,
    canRequestRollover ABSENT,
    encryptionKey OPTIONAL,
    verifyKeyIndicator (WITH COMPONENTS {
      reconstructionValue (WITH COMPONENTS {
        compressed-y-0, compressed-y-1
      })
    })
  })
})

---
-- @brief This data type defines an On-Board Equipment's (OBE) pseudonym
--        certificate structure and its contents. The RA brokers the
--        communication for provisioning this certificate from PCA to the OBE.
-- @class ObePseudonymCertificate
-- @param issuer     contains the hash of the certificate contents.
-- @param toBeSigned contains certificate content that is signed by the OBE.
-- @see IssuerIdentifier
ObePseudonymCertificate ::= ImplicitCertificate (WITH COMPONENTS { ...,
  issuer (WITH COMPONENTS {sha256AndDigest}),
  toBeSigned (WITH COMPONENTS { ...,
    id (WITH COMPONENTS { 
      linkageData (WITH COMPONENTS {
        group-linkage-value PRESENT
      })
    }),
    cracaId, --set to HashedId3 of the Root CA cert
    crlSeries(ObePseudonymCrlSeries),
    validityPeriod (WITH COMPONENTS { ...,
      duration (ObePseudonymCertExpiration)
    }),
    region (WITH COMPONENTS {
      identifiedRegion (SequenceOfIdentifiedRegion (SIZE(1)) (CONSTRAINED BY {
        IdentifiedRegion ( WITH COMPONENTS { countryOnly(USA) })
      }))
    }),
    assuranceLevel ABSENT,
    appPermissions (SequenceOfPsidSsp (SIZE(2)) (CONSTRAINED BY {
      PsidSsp (WITH COMPONENTS {
	    psid (BsmPsid), --PSID = 0x20
        ssp -- single OCTET STRING of length 0  
      }),
	  PsidSsp (WITH COMPONENTS {
		psid (MisbehaviorReportingPsid), -- PSID = 0x26
        ssp -- single OCTET STRING of length 0 
	  })
    })),
    certIssuePermissions ABSENT,
    certRequestPermissions ABSENT,
    canRequestRollover ABSENT,
    encryptionKey OPTIONAL,
    verifyKeyIndicator (WITH COMPONENTS {
      reconstructionValue (WITH COMPONENTS {
        compressed-y-0, compressed-y-1
      })
    })
  })
})

---
-- @brief This data type defines a Pseudonym Certificate Authority's (PCA) 
--        certificate structure and its contents generated by the ICA. The PCA 
--        provides a public key (encryptionKey) so that other SCMS components 
--        can send data securely to this PCA.
-- @class PcaCertificate
-- @param issuer     contains the hash of the certificate contents.
-- @param toBeSigned contains certificate content that is signed by the PCA.
-- @see IssuerIdentifier
PcaCertificate ::= ExplicitCertificate (WITH COMPONENTS { ...,
  issuer (WITH COMPONENTS {sha256AndDigest}),
  toBeSigned (WITH COMPONENTS { ...,
    id (WITH COMPONENTS {
      name ("pca.prod.v2xscms.com" | "pca.qa.v2xscms.com" | "pca.test.v2xscms.com")
    }),
    cracaId, --set to HashedId3 of the Root CA cert
    crlSeries(ScmsComponentCrlSeries),
    validityPeriod (WITH COMPONENTS { ...,
      duration (PcaCertExpiration)
    }),
    region (WITH COMPONENTS {
      identifiedRegion (SequenceOfIdentifiedRegion (SIZE(1)) (CONSTRAINED BY {
        IdentifiedRegion ( WITH COMPONENTS { countryOnly(USA) })
      }))
    }),
    assuranceLevel ABSENT,
    appPermissions (SequenceOfPsidSsp (SIZE(1)) (CONSTRAINED BY {
      PsidSsp (WITH COMPONENTS {
        psid (SecurityMgmtPsid), -- PSID = 0x23
        ssp --OER encoding of ScmsSsp indicating Pcassp
      })
    })),
    certIssuePermissions (SequenceOfPsidGroupPermissions (SIZE (1)) (WITH COMPONENT (WITH COMPONENTS {..., 
	  subjectPermissions (WITH COMPONENTS {..., 
		explicit (SequenceOfPsidSspRange (SIZE (26)) (CONSTRAINED BY{
          PsidSspRange (WITH COMPONENTS {
            psid (BsmPsid), --PSID = 0x20
            sspRange(WITH COMPONENTS{ 
              opaque -- single OCTET STRING of length 0  
            }) 
          }),
          PsidSspRange (WITH COMPONENTS {
            psid (MisbehaviorReportingPsid), -- PSID = 0x26
            sspRange ABSENT 
          }),
          PsidSspRange (WITH COMPONENTS {
            psid (VulnerableRoadUsersSafetyPsid), -- PSID = 0x27
            sspRange ABSENT 
          }),
          PsidSspRange (WITH COMPONENTS {
            psid (DifferentialGpsCorrectionsUncompressedPsid), -- PSID = 0x80 
            sspRange ABSENT 
          }),
          PsidSspRange (WITH COMPONENTS {
            psid (DifferentialGpsCorrectionsCompressedPsid), -- PSID = 0x81 
            sspRange ABSENT 
          }),
          PsidSspRange (WITH COMPONENTS {
            psid (IntersectionSafetyAndAwarenessPsid), -- PSID = 0x82 
            sspRange(WITH COMPONENTS{
              opaque --SSP: 90-01, 90-FF-FF-01, 90-FF-FF-02, 90-FF-FF-03, 90-FF-FF-04  
            }) 
          }),
          PsidSspRange (WITH COMPONENTS {
            psid (TravellerInformationAndRoadsideSignagePsid), -- PSID = 0x83 
            sspRange ABSENT 
          }),
          PsidSspRange (WITH COMPONENTS {
            psid (WaveServiceAdvertisementPsid), -- PSID = 0x87 
            sspRange(WITH COMPONENTS{
              opaque -- single OCTET STRING of length 0 
            }) 
          }),
          PsidSspRange (WITH COMPONENTS {
            psid (VehicleInitiatedDistressNotificationPsid), -- PSID = 0x4082
            sspRange ABSENT 
          }),
          PsidSspRange (WITH COMPONENTS {
            psid (TranscoreSoftwareUpdatePsid), -- PSID = 0x204083
            sspRange ABSENT 
          }),
          PsidSspRange (WITH COMPONENTS {
            psid (CVPApplication1Psid), -- PSID = 0x204088
            sspRange ABSENT 
          }),
          PsidSspRange (WITH COMPONENTS {
            psid (CVPApplication2Psid), -- PSID = 0x204089
            sspRange ABSENT 
          }),
          PsidSspRange (WITH COMPONENTS {
            psid (CVPApplication3Psid), -- PSID = 0x20408A
            sspRange ABSENT 
          }),
          PsidSspRange (WITH COMPONENTS {
            psid (CVPApplication4Psid), -- PSID = 0x20408B
            sspRange ABSENT 
          }),
          PsidSspRange (WITH COMPONENTS {
            psid (CVPApplication5Psid), -- PSID = 0x20408C
            sspRange ABSENT 
          }),
          PsidSspRange (WITH COMPONENTS {
            psid (CVPApplication6Psid), -- PSID = 0x20408D
            sspRange ABSENT 
          }),
          PsidSspRange (WITH COMPONENTS {
            psid (CVPApplication7Psid), -- PSID = 0x20408E
            sspRange ABSENT 
          }),
          PsidSspRange (WITH COMPONENTS {
            psid (CVPApplication8Psid), -- PSID = 0x20408F
            sspRange ABSENT 
          }),
          PsidSspRange (WITH COMPONENTS {
            psid (CVPApplication9Psid), -- PSID = 0x204090
            sspRange ABSENT 
          }),
          PsidSspRange (WITH COMPONENTS {
            psid (CVPApplication10Psid), -- PSID = 0x204091
            sspRange ABSENT 
          }),
          PsidSspRange (WITH COMPONENTS {
            psid (CVPApplication11Psid), -- PSID = 0x204092
            sspRange ABSENT 
          }),
          PsidSspRange (WITH COMPONENTS {
            psid (CVPApplication12Psid), -- PSID = 0x204093
            sspRange ABSENT 
          }),
          PsidSspRange (WITH COMPONENTS {
            psid (CVPApplication13Psid), -- PSID = 0x204094
            sspRange ABSENT 
          }),
          PsidSspRange (WITH COMPONENTS {
            psid (CVPApplication14Psid), -- PSID = 0x204095
            sspRange ABSENT 
          }),
          PsidSspRange (WITH COMPONENTS {
            psid (CVPApplication15Psid), -- PSID = 0x204096
            sspRange ABSENT 
          }),
          PsidSspRange (WITH COMPONENTS {
            psid (CVPApplication16Psid), -- PSID = 0x204097
            sspRange ABSENT 
          })
        }))
	  }),
	  minChainDepth(1), chainDepthRange(0),
      eeType({app})
    }))),
    certRequestPermissions ABSENT,
    canRequestRollover (NULL),
    encryptionKey PRESENT,
    verifyKeyIndicator (WITH COMPONENTS {
      verificationKey (WITH COMPONENTS {
        ecdsaNistP256 (WITH COMPONENTS {
          compressed-y-0, compressed-y-1
        })
      })
    })
  })
})

---
-- @brief This data type defines a Policy Generator's (PG) certificate 
--        structure and its contents generated by the Root CA.
-- @class PgCertificate
-- @param issuer     contains the hash of the certificate contents.
-- @param toBeSigned contains certificate content that is signed by the PG.
-- @see IssuerIdentifier
PgCertificate ::= ExplicitCertificate (WITH COMPONENTS { ...,
  issuer (WITH COMPONENTS {sha256AndDigest}),
  toBeSigned (WITH COMPONENTS { ...,
    id (WITH COMPONENTS {
      name ("pg.prod.v2xscms.com" | "pg.qa.v2xscms.com" | "pg.test.v2xscms.com")
    }),
    cracaId, --set to HashedId3 of the Root CA cert
    crlSeries(ScmsSpclComponentCrlSeries),
    validityPeriod (WITH COMPONENTS { ...,
      duration (PgCertExpiration)
    }),
    region ABSENT,
    assuranceLevel ABSENT,
    appPermissions (SequenceOfPsidSsp (SIZE(1)) (CONSTRAINED BY {
      PsidSsp (WITH COMPONENTS {
        psid (SecurityMgmtPsid), -- PSID = 0x23
        ssp --OER encoding of ScmsSsp indicating Policy Generator
      })
    })),
    certIssuePermissions ABSENT,
    certRequestPermissions ABSENT,
    canRequestRollover (NULL),
    encryptionKey ABSENT,
    verifyKeyIndicator (WITH COMPONENTS {
      verificationKey (WITH COMPONENTS {
        ecdsaNistP256 (WITH COMPONENTS {
          compressed-y-0, compressed-y-1
        })
      })
    })
  })
})

---
-- @brief This data type defines a Registration Authority's (RA) certificate 
--        structure and its contents generated by the ICA. The RA provides a 
--        public key (encryptionKey) so that other SCMS components can send
--        data securely to this RA.
-- @class RaCertificate
-- @param issuer     contains the hash of the certificate contents.
-- @param toBeSigned contains certificate content that is signed by the RA.
-- @see IssuerIdentifier
RaCertificate ::= ExplicitCertificate (WITH COMPONENTS { ...,
  issuer (WITH COMPONENTS{sha256AndDigest}),
  toBeSigned (WITH COMPONENTS { ...,
    id (WITH COMPONENTS {
      name ("ra.prod.v2xscms.com" | "ra.qa.v2xscms.com" | "ra.test.v2xscms.com")
    }),
    cracaId, --set to HashedId3 of the Root CA cert
    crlSeries(ScmsComponentCrlSeries),
    validityPeriod (WITH COMPONENTS { ...,
      duration (RaCertExpiration)
    }),
    region (WITH COMPONENTS {
      identifiedRegion (SequenceOfIdentifiedRegion (SIZE(1)) (CONSTRAINED BY {
        IdentifiedRegion ( WITH COMPONENTS { countryOnly(USA) })
      }))
    }),
    assuranceLevel ABSENT,
    appPermissions (SequenceOfPsidSsp (SIZE(1)) (CONSTRAINED BY {
      PsidSsp (WITH COMPONENTS {
        psid (SecurityMgmtPsid), -- PSID = 0x23
        ssp --OER encoding of ScmsSsp indicating Rassp
      })
    })),
    certIssuePermissions ABSENT,
    certRequestPermissions (SequenceOfPsidGroupPermissions (SIZE (1)) (WITH COMPONENT (WITH COMPONENTS {..., 
	  subjectPermissions (WITH COMPONENTS {..., 
		explicit (SequenceOfPsidSspRange (SIZE (25)) (CONSTRAINED BY{
          PsidSspRange (WITH COMPONENTS {
            psid (BsmPsid), --PSID = 0x20
            sspRange(WITH COMPONENTS{ 
              opaque -- single OCTET STRING of length 0  
            }) 
          }),
          PsidSspRange (WITH COMPONENTS {
            psid (MisbehaviorReportingPsid), -- PSID = 0x26
            sspRange ABSENT 
          }),
          PsidSspRange (WITH COMPONENTS {
            psid (VulnerableRoadUsersSafetyPsid), -- PSID = 0x27
            sspRange ABSENT 
          }),
          PsidSspRange (WITH COMPONENTS {
            psid (DifferentialGpsCorrectionsUncompressedPsid), -- PSID = 0x80 
            sspRange ABSENT 
          }),
          PsidSspRange (WITH COMPONENTS {
            psid (DifferentialGpsCorrectionsCompressedPsid), -- PSID = 0x81 
            sspRange ABSENT 
          }),
          PsidSspRange (WITH COMPONENTS {
            psid (IntersectionSafetyAndAwarenessPsid), -- PSID = 0x82 
            sspRange(WITH COMPONENTS{
              opaque --SSP: 90-01, 90-FF-FF-01, 90-FF-FF-02, 90-FF-FF-03, 90-FF-FF-04  
            }) 
          }),
          PsidSspRange (WITH COMPONENTS {
            psid (TravellerInformationAndRoadsideSignagePsid), -- PSID = 0x83 
            sspRange ABSENT 
          }),
          PsidSspRange (WITH COMPONENTS {
            psid (WaveServiceAdvertisementPsid), -- PSID = 0x87 
            sspRange(WITH COMPONENTS{
              opaque -- single OCTET STRING of length 0 
            }) 
          }),
          PsidSspRange (WITH COMPONENTS {
            psid (VehicleInitiatedDistressNotificationPsid), -- PSID = 0x4082
            sspRange ABSENT 
          }),
          PsidSspRange (WITH COMPONENTS {
            psid (TranscoreSoftwareUpdatePsid), -- PSID = 0x204083
            sspRange ABSENT 
          }),
          PsidSspRange (WITH COMPONENTS {
            psid (CVPApplication1Psid), -- PSID = 0x204088
            sspRange ABSENT 
          }),
          PsidSspRange (WITH COMPONENTS {
            psid (CVPApplication2Psid), -- PSID = 0x204089
            sspRange ABSENT 
          }),
          PsidSspRange (WITH COMPONENTS {
            psid (CVPApplication3Psid), -- PSID = 0x20408A
            sspRange ABSENT 
          }),
          PsidSspRange (WITH COMPONENTS {
            psid (CVPApplication4Psid), -- PSID = 0x20408B
            sspRange ABSENT 
          }),
          PsidSspRange (WITH COMPONENTS {
            psid (CVPApplication5Psid), -- PSID = 0x20408C
            sspRange ABSENT 
          }),
          PsidSspRange (WITH COMPONENTS {
            psid (CVPApplication6Psid), -- PSID = 0x20408D
            sspRange ABSENT 
          }),
          PsidSspRange (WITH COMPONENTS {
            psid (CVPApplication7Psid), -- PSID = 0x20408E
            sspRange ABSENT 
          }),
          PsidSspRange (WITH COMPONENTS {
            psid (CVPApplication8Psid), -- PSID = 0x20408F
            sspRange ABSENT 
          }),
          PsidSspRange (WITH COMPONENTS {
            psid (CVPApplication9Psid), -- PSID = 0x204090
            sspRange ABSENT 
          }),
          PsidSspRange (WITH COMPONENTS {
            psid (CVPApplication10Psid), -- PSID = 0x204091
            sspRange ABSENT 
          }),
          PsidSspRange (WITH COMPONENTS {
            psid (CVPApplication11Psid), -- PSID = 0x204092
            sspRange ABSENT 
          }),
          PsidSspRange (WITH COMPONENTS {
            psid (CVPApplication12Psid), -- PSID = 0x204093
            sspRange ABSENT 
          }),
          PsidSspRange (WITH COMPONENTS {
            psid (CVPApplication13Psid), -- PSID = 0x204094
            sspRange ABSENT 
          }),
          PsidSspRange (WITH COMPONENTS {
            psid (CVPApplication14Psid), -- PSID = 0x204095
            sspRange ABSENT 
          }),
          PsidSspRange (WITH COMPONENTS {
            psid (CVPApplication15Psid), -- PSID = 0x204096
            sspRange ABSENT 
          }),
          PsidSspRange (WITH COMPONENTS {
            psid (CVPApplication16Psid), -- PSID = 0x204097
            sspRange ABSENT 
          })
        }))
	  }),
	  minChainDepth(0), chainDepthRange(0),
      eeType({app})
    }))),
    canRequestRollover(NULL),
    encryptionKey PRESENT,
    verifyKeyIndicator (WITH COMPONENTS {
      verificationKey (WITH COMPONENTS {
        ecdsaNistP256 (WITH COMPONENTS {
          compressed-y-0, compressed-y-1
        })
      })
    })
  })
})

---
-- @brief This data type defines a Root Certificate Authority's (RCA) certificate 
--        structure and its contents generated by the SCMS Manager.
-- @class RcaCertificate
-- @param issuer     contains the hash of the certificate contents.
-- @param toBeSigned contains certificate content that is signed by the RCA.
-- @see IssuerIdentifier
RootCaCertificate ::= ExplicitCertificate (WITH COMPONENTS { ...,
  issuer (WITH COMPONENTS {self}),
  toBeSigned (WITH COMPONENTS { ...,
    id (WITH COMPONENTS {
      name ("v2xrootca.ghsiss.com" | "rca.qa.v2xscms.com" | "rca.test.v2xscms.com")
    }),
    cracaId('000000'H),
    crlSeries(0),                          
    validityPeriod (WITH COMPONENTS { ...,
      duration (RootCaCertExpiration)
    }),
    region ABSENT,
    assuranceLevel ABSENT,
    appPermissions (SequenceOfPsidSsp (SIZE(2)) (CONSTRAINED BY {
      PsidSsp (WITH COMPONENTS {
        psid (SecurityMgmtPsid), -- PSID = 0x23
        ssp --OER encoding of ScmsSsp indicating RootCaSsp
      }),
      PsidSsp (WITH COMPONENTS {
        psid (CrlPsid), -- PSID = 0x100
        ssp (WITH COMPONENTS {opaque(CONTAINING CrlSsp (WITH COMPONENTS {..., 
          associatedCraca(isCraca),
          crls (PermissibleCrls (SIZE(1)) (CONSTRAINED BY {
            CrlSeries (ScmsSpclComponentCrlSeries)
          }))
        }))})
      })
    })),
    certIssuePermissions (SequenceOfPsidGroupPermissions (SIZE(4)) (CONSTRAINED BY {
      PsidGroupPermissions ( WITH COMPONENTS {..., 
	    subjectPermissions (WITH COMPONENTS { 
          all
        }),
        minChainDepth(3), 
        chainDepthRange(-1),
        eeType ({app, enrol})
      }),
      PsidGroupPermissions ( WITH COMPONENTS {..., 
	    subjectPermissions (WITH COMPONENTS{ 
          explicit (SequenceOfPsidSspRange (SIZE (1)) (WITH COMPONENT (WITH COMPONENTS {
            psid (SecurityMgmtPsid), -- PSID = 0x23
            sspRange ABSENT 
          })))
        }),
        minChainDepth(1), 
        chainDepthRange(-1), 
	    eeType ({app, enrol}) 
      }),
      PsidGroupPermissions ( WITH COMPONENTS {..., 
	    subjectPermissions (WITH COMPONENTS{ 
          explicit (SequenceOfPsidSspRange (SIZE (1)) (WITH COMPONENT (WITH COMPONENTS {
            psid (MisbehaviorReportingPsid), -- PSID = 0x26
            sspRange ABSENT 
          })))
        }),
        minChainDepth(1), 
        chainDepthRange(-1), 
	    eeType ({app, enrol}) 
      }),
      PsidGroupPermissions ( WITH COMPONENTS {..., 
	    subjectPermissions (WITH COMPONENTS{ 
          explicit (SequenceOfPsidSspRange (SIZE (1)) (WITH COMPONENT (WITH COMPONENTS {
            psid (CrlPsid), -- PSID = 0x100
            sspRange ABSENT 
          })))
        }),
        minChainDepth(1), 
        chainDepthRange(-1), 
	    eeType ({app, enrol}) 
      })                      
    })),
    certRequestPermissions ABSENT,
    canRequestRollover ABSENT,
    encryptionKey ABSENT,
    verifyKeyIndicator (WITH COMPONENTS {
      verificationKey (WITH COMPONENTS {
        ecdsaNistP256 (WITH COMPONENTS {
          compressed-y-0, compressed-y-1
        })
      })
    })
  })
})

---
-- @brief This data type defines a Road-Side Equipment's (RSE) application
--        certificate structure and its contents. The RA brokers the
--        communication for provisioning this certificate from PCA to the RSE.
-- @class RseApplicationCertificate
-- @param issuer     contains the hash of the certificate contents.
-- @param toBeSigned contains certificate content that is signed by the RSE.
-- @see IssuerIdentifier
RseApplicationCertificate ::= ImplicitCertificate (WITH COMPONENTS { ...,
  issuer (WITH COMPONENTS {sha256AndDigest}),
    toBeSigned (WITH COMPONENTS { ...,
      id (WITH COMPONENTS {
        binaryId (SIZE (8))  -- RIF value shall be used as the certificate ID
      }),
    cracaId, --set to HashedId3 of the Root CA cert
    crlSeries(EeNonPseudonymCrlSeries),
    validityPeriod (WITH COMPONENTS { ...,
      duration (RseApplicationCertExpiration)
    }),
    region (WITH COMPONENTS {
      identifiedRegion (SequenceOfIdentifiedRegion (SIZE(1)) (CONSTRAINED BY {
        IdentifiedRegion ( WITH COMPONENTS { countryOnly(USA) })
      }))
    }),
    assuranceLevel ABSENT,
    --appPermissions TO BE SPECIFIED BY SCMS MANAGER,
    certIssuePermissions ABSENT,
    certRequestPermissions ABSENT,
    canRequestRollover ABSENT,
    encryptionKey OPTIONAL,
    verifyKeyIndicator (WITH COMPONENTS {
      reconstructionValue (WITH COMPONENTS {
        compressed-y-0, compressed-y-1
      })
    })
  })
})

---
-- @brief This data type defines an Road-Side Equipment's (RSE) enrollment 
--        certificate structure and its contents. The ECA provides this
--        certificate on request from the DCM while bootstrapping the device.
-- @class RseEnrollmentCertificate
-- @param issuer     contains the hash of the certificate contents.
-- @param toBeSigned contains certificate content that is signed by the RSE.
-- @see IssuerIdentifier
RseEnrollmentCertificate ::= ImplicitCertificate (WITH COMPONENTS { ...,
  issuer (WITH COMPONENTS{sha256AndDigest}),
  toBeSigned (WITH COMPONENTS { ...,
    id (WITH COMPONENTS { 
      name("")
    }),
    cracaId, --set to HashedId3 of the Root CA cert
    crlSeries(EeEnrollmentCrlSeries),
    validityPeriod (WITH COMPONENTS { ...,
      duration (RseEnrollmentCertExpirationPoc | RseEnrollmentCertExpirationCvp)
    }),
    region (WITH COMPONENTS {
      identifiedRegion (SequenceOfIdentifiedRegion (SIZE(1)) (CONSTRAINED BY {
        IdentifiedRegion ( WITH COMPONENTS { countryOnly(USA) })
      }))
    }),
    assuranceLevel ABSENT,
    appPermissions ABSENT,
    certIssuePermissions ABSENT,
    --certRequestPermissions TO BE SPECIFIED BY SCMS MANAGER,
    canRequestRollover(NULL),
    encryptionKey ABSENT,
    verifyKeyIndicator (WITH COMPONENTS {
      reconstructionValue (WITH COMPONENTS {
        compressed-y-0, compressed-y-1
      })
    })
  })
})

END
