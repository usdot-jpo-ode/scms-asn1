-- 
--  Copyright 2017 Crash Avoidance Metrics Partner, VSC5 Consortium
-- 
--  Licensed under the Apache License, Version 2.0 (the "License");
--  you may not use this file except in compliance with the License.
--  You may obtain a copy of the License at
-- 
--     http://www.apache.org/licenses/LICENSE-2.0
-- 
--  Unless required by applicable law or agreed to in writing, software
--  distributed under the License is distributed on an "AS IS" BASIS,
--  WITHOUT WARRANTIES OR CONDITIONS OF ANY KIND, either express or implied.
--  See the License for the specific language governing permissions and
--  limitations under the License.
-- 

-- @namespace Ieee1609dot2ScmsError 
Ieee1609dot2ScmsError {iso(1) identified-organization(3) ieee(111)
standards-association-numbered-series-standards(2) wave-stds(1609)  dot2(2)
scms (2) errors(2) complete (1)}


DEFINITIONS AUTOMATIC TAGS ::= BEGIN 

EXPORTS ALL;

IMPORTS 

  ScmsCommonError
FROM Ieee1609dot2ScmsCommonError {iso(1) identified-organization(3) ieee(111)
standards-association-numbered-series-standards(2) wave-stds(1609) dot2(2)
scms (2) errors(2) common(2)}

  ComponentCertificateManagementError
FROM Ieee1609Dot2ScmsComponentCertificateManagementErrorScmsComponentCertificateManagementError
    {iso(1) identified-organization(3) ieee(111) 
    standards-association-numbered-series-standards(2) wave-stds(1609)  
    dot2(2) scms(2) errors(2) component-certificate-management(3)}

  EcaEndEntityError
FROM Ieee1609Dot2EcaEndEntityErrorEcaEndEntityError
    {iso(1) identified-organization(3) ieee(111) 
    standards-association-numbered-series-standards(2) wave-stds(1609)  
    dot2(2) scms(2) errors(2) eca-ee(5)}

  LaMaError
FROM Ieee1609Dot2LaMaErrorLaMaError
    {iso(1) identified-organization(3) ieee(111) 
    standards-association-numbered-series-standards(2) wave-stds(1609)  
    dot2(2) scms(2) errors(2) la-ma(9)}

  LaPcaError
FROM Ieee1609Dot2LaPcaErrorLaPcaError
    {iso(1) identified-organization(3) ieee(111) 
    standards-association-numbered-series-standards(2) wave-stds(1609)  
    dot2(2) scms(2) errors(2) la-pca(10)}

  LaRaError
FROM Ieee1609Dot2LaRaErrorLaRaError
    {iso(1) identified-organization(3) ieee(111) 
    standards-association-numbered-series-standards(2) wave-stds(1609)  
    dot2(2) scms(2) errors(2) la-ra(11)}

  MaPcaError
FROM Ieee1609Dot2MaPcaErrorMaPcaError
    {iso(1) identified-organization(3) ieee(111) 
    standards-association-numbered-series-standards(2) wave-stds(1609)  
    dot2(2) scms(2) errors(2) ma-pca(13)}

  MaRaError
FROM Ieee1609Dot2MaRaErrorMaRaError
    {iso(1) identified-organization(3) ieee(111) 
    standards-association-numbered-series-standards(2) wave-stds(1609)  
    dot2(2) scms(2) errors(2) ma-ra(14)}

  PcaRaError
FROM Ieee1609Dot2PcaRaErrorPcaRaError
    {iso(1) identified-organization(3) ieee(111) 
    standards-association-numbered-series-standards(2) wave-stds(1609)  
    dot2(2) scms(2) errors(2) pca-ra(15)}

;

---
-- @brief 
-- @class ScmsError 
-- @param
-- @see 
ScmsError ::= CHOICE {
  common  ScmsCommonError,
  ccm     ComponentCertificateManagementError,
  eca-ee  EcaEndEntityError,
  la-ma   LaMaError,
  la-pca  LaPcaError,
  la-ra   LaRaError,
  ma-pca  MaPcaError,
  ma-ra   MaRaError,
  pca-ra  PcaRaError,
  ...
}


---
-- @brief 
-- @class ScopedComponentCertificateManagementError 
-- @param
-- @see 
ScopedComponentCertificateManagementError ::= 
  ScmsError (WITH COMPONENTS {common} | WITH COMPONENTS {ccm})

---
-- @brief 
-- @class ScopedEcaEndEntityError 
-- @param
-- @see 
ScopedEcaEndEntityError ::= 
  ScmsError (WITH COMPONENTS {common} | WITH COMPONENTS {eca-ee})

-- This type is not used (see following la-ma errors)
---
-- @brief 
-- @class ScopedLaMaError 
-- @param
-- @see 
ScopedLaMaError ::=
  ScmsError (WITH COMPONENTS {common} | WITH COMPONENTS {la-ma})
-- Linkage information request errors
---
-- @brief 
-- @class ScopedLaMaLIError 
-- @param
-- @see 
ScopedLaMaLIError ::=
  ScmsError (WITH COMPONENTS {common} | 
             WITH COMPONENTS {la-ma 
                (WITH COMPONENTS {la-ma-base-error} |
                 WITH COMPONENTS {la-ma-linkage-info-error})}
            )
-- Linkage seed request errors
---
-- @brief 
-- @class ScopedLaMaLSError 
-- @param
-- @see 
ScopedLaMaLSError ::=
  ScmsError (WITH COMPONENTS {common} | 
             WITH COMPONENTS {la-ma 
                (WITH COMPONENTS {la-ma-base-error} |
                 WITH COMPONENTS {la-ma-linkage-seed-error})}
            )

---
-- @brief 
-- @class ScopedLaPcaError 
-- @param
-- @see 
ScopedLaPcaError ::= 
  ScmsError (WITH COMPONENTS {common} | WITH COMPONENTS {la-pca})

---
-- @brief 
-- @class ScopedLaRaError 
-- @param
-- @see 
ScopedLaRaError ::= 
  ScmsError (WITH COMPONENTS {common} | WITH COMPONENTS {la-ra})

---
-- @brief 
-- @class ScopedMaPcaError 
-- @param
-- @see 
ScopedMaPcaError ::= 
  ScmsError (WITH COMPONENTS {common} | WITH COMPONENTS {ma-pca})

---
-- @brief 
-- @class ScopedMaRaError 
-- @param
-- @see 
ScopedMaRaError ::= 
  ScmsError (WITH COMPONENTS {common} | WITH COMPONENTS {ma-ra})
-- Blacklist request errors
---
-- @brief 
-- @class ScopedMaRaBlacklistError 
-- @param
-- @see 
ScopedMaRaBlacklistError ::=
  ScmsError (WITH COMPONENTS {common} | 
             WITH COMPONENTS {ma-ra
                (WITH COMPONENTS {ma-ra-base-error} |
                 WITH COMPONENTS {ma-ra-blacklist-error})}
            )
-- Linkage chain identifier request errors
---
-- @brief 
-- @class ScopedMaRaLCIError 
-- @param
-- @see 
ScopedMaRaLCIError ::=
  ScmsError (WITH COMPONENTS {common} | 
             WITH COMPONENTS {ma-ra
                (WITH COMPONENTS {ma-ra-base-error} |
                 WITH COMPONENTS {ma-ra-lci-error})}
            )



---
-- @brief 
-- @class ScopedPcaRaError 
-- @param
-- @see 
ScopedPcaRaError ::= 
  ScmsError (WITH COMPONENTS {common} | WITH COMPONENTS {pca-ra})


END
